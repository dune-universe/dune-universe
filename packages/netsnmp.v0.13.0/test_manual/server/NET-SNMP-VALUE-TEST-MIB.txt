NET-SNMP-VALUE-TEST-MIB DEFINITIONS ::= BEGIN

--
-- Example MIB objects for agent module example implementations
--

IMPORTS
    MODULE-IDENTITY, OBJECT-TYPE, Integer32,
    NOTIFICATION-TYPE                       FROM SNMPv2-SMI
    SnmpAdminString                         FROM SNMP-FRAMEWORK-MIB
    netSnmp                                 FROM NET-SNMP-MIB
    RowStatus, StorageType                  FROM SNMPv2-TC
    InetAddressType, InetAddress            FROM INET-ADDRESS-MIB
;

netSnmpExamples MODULE-IDENTITY
    LAST-UPDATED "200406150000Z"
    ORGANIZATION "www.net-snmp.org"
    CONTACT-INFO    
	 "postal:   Wes Hardaker
                    P.O. Box 382
                    Davis CA  95617

          email:    net-snmp-coders@lists.sourceforge.net"
    DESCRIPTION
	"Example MIB objects for agent module example implementations"
    REVISION     "200406150000Z"
    DESCRIPTION
	"Corrected notification example definitions"
    REVISION     "200202060000Z"
    DESCRIPTION
	"First draft"
    ::= { netSnmp 2 }

netSnmpValueTest            OBJECT IDENTIFIER ::= { netSnmpExamples 99 }

netSnmpValueTestInteger32 OBJECT-TYPE
    SYNTAX      Integer32
    MAX-ACCESS  read-only
    STATUS      current
    DESCRIPTION
	"An Integer32 value"
    ::= { netSnmpValueTest 1 }

netSnmpValueTestGauge OBJECT-TYPE
    SYNTAX      Gauge
    MAX-ACCESS  read-only
    STATUS      current
    DESCRIPTION
	"A Gauge value"
    ::= { netSnmpValueTest 2 }

netSnmpValueTestCounter OBJECT-TYPE
    SYNTAX      Counter
    MAX-ACCESS  read-only
    STATUS      current
    DESCRIPTION
	"A Counter value"
    ::= { netSnmpValueTest 3 }

netSnmpValueTestCounter64 OBJECT-TYPE
    SYNTAX      Counter64
    MAX-ACCESS  read-only
    STATUS      current
    DESCRIPTION
	"A Counter64 value"
    ::= { netSnmpValueTest 4 }

netSnmpValueTestTimeticks OBJECT-TYPE
    SYNTAX      TimeTicks
    MAX-ACCESS  read-only
    STATUS      current
    DESCRIPTION
	"A Timeticks value"
    ::= { netSnmpValueTest 5 }

netSnmpValueTestUnsigned32 OBJECT-TYPE
    SYNTAX      Unsigned32
    MAX-ACCESS  read-only
    STATUS      current
    DESCRIPTION
	"An Unsigned32 value"
    ::= { netSnmpValueTest 6 }

netSnmpValueTestIpAddress OBJECT-TYPE
    SYNTAX      IpAddress
    MAX-ACCESS  read-only
    STATUS      current
    DESCRIPTION
	"An IpAddress value"
    ::= { netSnmpValueTest 7 }

netSnmpValueTestOpaque OBJECT-TYPE
    SYNTAX      Opaque
    MAX-ACCESS  read-only
    STATUS      current
    DESCRIPTION
	"An Opaque value"
    ::= { netSnmpValueTest 8 }

netSnmpValueTestObjectID OBJECT-TYPE
    SYNTAX      OBJECT IDENTIFIER
    MAX-ACCESS  read-only
    STATUS      current
    DESCRIPTION
	"An ObjectID value"
    ::= { netSnmpValueTest 9 }

netSnmpValueTestBitString OBJECT-TYPE
    SYNTAX      BITS { Bit0(0), Bit1(1), Bit2(2) }
    MAX-ACCESS  read-only
    STATUS      current
    DESCRIPTION
	"A BitString value"
    ::= { netSnmpValueTest 10 }

netSnmpValueTestOctetString OBJECT-TYPE
    SYNTAX      OCTET STRING
    MAX-ACCESS  read-only
    STATUS      current
    DESCRIPTION
	"A OctetString value"
    ::= { netSnmpValueTest 11 }

netSnmpValueTestOpaqueCounter64 OBJECT-TYPE
    SYNTAX      Opaque (SIZE(8))
    MAX-ACCESS  read-only
    STATUS      current
    DESCRIPTION
	"An OpaqueCounter64 value"
    ::= { netSnmpValueTest 12 }

netSnmpValueTestOpaqueU64 OBJECT-TYPE
    SYNTAX      Opaque (SIZE(8))
    MAX-ACCESS  read-only
    STATUS      current
    DESCRIPTION
	"An OpaqueU64 value"
    ::= { netSnmpValueTest 13 }

netSnmpValueTestOpaqueI64 OBJECT-TYPE
    SYNTAX      Opaque (SIZE(8))
    MAX-ACCESS  read-only
    STATUS      current
    DESCRIPTION
	"An OpaqueI64 value"
    ::= { netSnmpValueTest 14 }

netSnmpValueTestOpaqueFloat OBJECT-TYPE
    SYNTAX      Opaque (SIZE(4))
    MAX-ACCESS  read-only
    STATUS      current
    DESCRIPTION
	"An OpaqueFloat value"
    ::= { netSnmpValueTest 15 }

netSnmpValueTestOpaqueDouble OBJECT-TYPE
    SYNTAX      Opaque (SIZE(8))
    MAX-ACCESS  read-only
    STATUS      current
    DESCRIPTION
	"An OpaqueDouble value"
    ::= { netSnmpValueTest 16 }

END
